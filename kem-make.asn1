KEM-MAKE-2026 DEFINITIONS IMPLICIT TAGS ::=
BEGIN

-- ===========================================================================
-- KEM-MAKE protocol message syntax.
--
-- Encoding: DER only. BER (indefinite lengths, non-minimal length forms,
-- non-canonical constructed/primitive forms) is not permitted on the wire.
-- ===========================================================================

IMPORTS
    AlgorithmIdentifier{}, ALGORITHM, DIGEST-ALGORITHM
    FROM AlgorithmInformation-2009
        { iso(1) identified-organization(3) dod(6) internet(1)
          security(5) mechanisms(5) pkix(7) id-mod(0)
          id-mod-algorithmInformation-02(58) }
    mda-sha256
    FROM PKIX1-PSS-OAEP-Algorithms-2009
        { iso(1) identified-organization(3) dod(6) internet(1)
          security(5) mechanisms(5) pkix(7) id-mod(0)
          id-mod-pkix1-rsa-pkalgs-02(54) };

-- ML-KEM OIDs (RFC 9935). parameters MUST be absent for all three, not
-- NULL; hence "PARAMS ARE absent" with no TYPE at all, rather than
-- "PARAMS TYPE NULL ARE absent". This specific form (an open type with no
-- associated type for some objects in the set) is the exact construct
-- disputed by RFC 5912 errata 4145, which argues it isn't well-formed
-- ASN.1. Written this way anyway because it's what ML-KEM's actual
-- requirement is: "PARAMS TYPE NULL ARE absent" would be internally
-- consistent ASN.1 but would misdescribe the wire format (implying a
-- NULL type is merely never chosen, rather than that no type applies at
-- all).
id-alg-ml-kem-512  OBJECT IDENTIFIER ::= { 2 16 840 1 101 3 4 4 1 }
id-alg-ml-kem-768  OBJECT IDENTIFIER ::= { 2 16 840 1 101 3 4 4 2 }
id-alg-ml-kem-1024 OBJECT IDENTIFIER ::= { 2 16 840 1 101 3 4 4 3 }

mlkem-512 ALGORITHM ::= {
    IDENTIFIER id-alg-ml-kem-512
    PARAMS ARE absent
}
mlkem-768 ALGORITHM ::= {
    IDENTIFIER id-alg-ml-kem-768
    PARAMS ARE absent
}
mlkem-1024 ALGORITHM ::= {
    IDENTIFIER id-alg-ml-kem-1024
    PARAMS ARE absent
}

-- Locally defined object set, since ML-KEM postdates RFC 5912 by over a
-- decade and no PKIX module defines it. This follows RFC 5912's own
-- documented pattern for adding algorithms it doesn't cover (see e.g.
-- PKInfoAlgorithms/SignatureAlgorithms placeholder object sets in RFC
-- 5912 Section 4, explicitly commented "add any locally defined
-- algorithms here").
MlkemAlgorithms ALGORITHM ::= { mlkem-512 | mlkem-768 | mlkem-1024, ... }

KemPublicKey ::= SEQUENCE {
    algorithm  AlgorithmIdentifier{ALGORITHM, {MlkemAlgorithms}},
    publicKey  OCTET STRING           -- length fixed by algorithm (FIPS 203)
}

KemCiphertext ::= SEQUENCE {
    algorithm   AlgorithmIdentifier{ALGORITHM, {MlkemAlgorithms}},
    ciphertext  OCTET STRING          -- length fixed by algorithm (FIPS 203)
}

-- Digest algorithm for KeyId. mda-sha256 is imported directly rather than
-- the broader "HashAlgs" object set exported by either PKIXAlgs-2009 or
-- PKIX1-PSS-OAEP-Algorithms-2009 (both use that same name for materially
-- different sets; RFC 5912 itself calls out module-qualifying object
-- set names for exactly this reason), since we only ever need SHA-256
-- today. Extensible (", ...") so a future digest can be added without
-- reworking the schema.
KemMakeHashAlgorithms DIGEST-ALGORITHM ::= { mda-sha256, ... }

-- Key identifier: digest algorithm + hash of the DER encoding of the whole
-- KemPublicKey SEQUENCE (algorithm + key bytes), never the raw key octets
-- alone. hashAlgorithm identifies how keyHash was computed; it says nothing
-- about the KEM algorithm of the underlying key.
KeyId ::= SEQUENCE {
    hashAlgorithm  AlgorithmIdentifier{DIGEST-ALGORITHM, {KemMakeHashAlgorithms}},
    keyHash        OCTET STRING
}

-- === section ===
-- MAKE protocol PDUs
-- === section ===

-- AEAD algorithm OIDs used for negotiation only: a bare OBJECT IDENTIFIER,
-- not a full AlgorithmIdentifier. AES-GCM (RFC 5084) normally requires a
-- present parameters field with actual nonce/ICV-length data when used as
-- a real AlgorithmIdentifier for encryption; that requirement does not
-- apply here, since these fields only carry the OID for capability
-- negotiation, analogous to how RFC 8103 defines SMIMECapability
-- announcement (OID only, parameters omitted).
id-aes128-gcm           OBJECT IDENTIFIER ::= { 2 16 840 1 101 3 4 1 6 }
id-aes192-gcm           OBJECT IDENTIFIER ::= { 2 16 840 1 101 3 4 1 26 }
id-aes256-gcm           OBJECT IDENTIFIER ::= { 2 16 840 1 101 3 4 1 46 }
id-chacha20-poly1305    OBJECT IDENTIFIER ::= { 1 2 840 113549 1 9 16 3 18 }

AcceptableAeadList ::= SEQUENCE OF OBJECT IDENTIFIER

SessionInitRequest ::= SEQUENCE {
    ct1               KemCiphertext,
    keyIdB            KeyId,           -- identifies the recipient key ct1 was encapsulated against
    pkAStar           KemPublicKey,
    keyIdA            KeyId,
    acceptableAeads   AcceptableAeadList
}

SessionInitResponse ::= SEQUENCE {
    keyIdB      KeyId,
    pkBStar     KemPublicKey,
    ct2         KemCiphertext,
    ct3         KemCiphertext,
    nB          OCTET STRING,
    chosenAead  OBJECT IDENTIFIER
}

SessionCompletionRequest ::= SEQUENCE {
    cM          OCTET STRING,
    ct4         KemCiphertext,
    nA          OCTET STRING,
    m       [0] OCTET STRING OPTIONAL
}

SessionCompletionResponse ::= SEQUENCE {
    hM          OCTET STRING,
    m       [0] OCTET STRING OPTIONAL
}

-- seq is scoped per direction: each peer keeps its own independent
-- counter, so the same seq value can legitimately appear once from each
-- peer within a session. This is safe because each direction has its own
-- independently derived session key (from the same HKDF that produces
-- the other session key material); the pair (direction key, seq) is what
-- must be unique, not seq alone.
Message ::= SEQUENCE {
    seq  INTEGER,
    m    OCTET STRING
}

MakePayload ::= CHOICE {
    sessionInitRequest        [0] SessionInitRequest,
    sessionInitResponse       [1] SessionInitResponse,
    sessionCompletionRequest  [2] SessionCompletionRequest,
    sessionCompletionResponse [3] SessionCompletionResponse,
    message                   [4] Message
}

-- Versioned session envelope. version defaults to 0 (protocol v1) and, per
-- DER, MUST be omitted from the encoding when equal to its default value.
-- cid is a 128-bit binary UUID (RFC 4122), fixed length, no ASN.1-level
-- length constraint expressed here beyond OCTET STRING; length is
-- enforced by the implementation, not the schema.
MakeMessage ::= SEQUENCE {
    version  INTEGER DEFAULT 0,
    cid      OCTET STRING (SIZE(16)),  -- 128-bit UUID (RFC 4122)
    payload  MakePayload
}

END
