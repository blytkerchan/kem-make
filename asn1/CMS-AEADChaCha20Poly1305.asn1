-- Vendored from RFC 8103, Appendix A ("ASN.1 Module"), verbatim.
-- https://www.rfc-editor.org/rfc/rfc8103
--
-- Kept here for its canonical id-alg-AEADChaCha20Poly1305 OID value,
-- which KEM-MAKE-2026.asn1 imports for AEAD capability negotiation
-- (bare OID only. See KEM-MAKE-2026.asn1's own comments for why the
-- AEADChaCha20Poly1305Nonce parameter type below doesn't apply there).

CMS-AEADChaCha20Poly1305
    { iso(1) member-body(2) us(840) rsadsi(113549) pkcs(1)
      pkcs-9(9) smime(16) modules(0) 66 }

DEFINITIONS IMPLICIT TAGS ::= BEGIN

IMPORTS
   CONTENT-ENCRYPTION
   FROM AlgorithmInformation-2009
       { iso(1) identified-organization(3) dod(6) internet(1)
         security(5) mechanisms(5) pkix(7) id-mod(0)
         id-mod-algorithmInformation-02(58) };

-- EXPORTS All

AEADContentEncryptionAlgs CONTENT-ENCRYPTION ::=
    { cea-AEADChaCha20Poly1305, ... }

cea-AEADChaCha20Poly1305 CONTENT-ENCRYPTION ::= {
    IDENTIFIER id-alg-AEADChaCha20Poly1305
    PARAMS TYPE AEADChaCha20Poly1305Nonce ARE required
    SMIME-CAPS { IDENTIFIED BY id-alg-AEADChaCha20Poly1305 } }

id-alg-AEADChaCha20Poly1305 OBJECT IDENTIFIER ::=
    { iso(1) member-body(2) us(840) rsadsi(113549) pkcs(1)
      pkcs9(9) smime(16) alg(3) 18 }

AEADChaCha20Poly1305Nonce ::= OCTET STRING (SIZE(12))

END
